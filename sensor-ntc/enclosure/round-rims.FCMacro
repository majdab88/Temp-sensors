# -*- coding: utf-8 -*-
# ============================================================
# round-rims — soften the horizontal rims of the enclosure
#
# The vertical corners are already rounded by the sketches in
# sensor-ntc-v2-enclosure.FCMacro. The horizontal rims can't be:
# rounding a top or bottom face perimeter needs a real 3D fillet.
#
# Run this on a document built by that macro, with the enclosure
# document active. Radius comes from the 'edge_r' cell of the
# params spreadsheet, so change it there and re-run.
#
# RE-RUN AFTER ANY DIMENSION CHANGE. A PartDesign Fillet stores the
# edge names it was handed, and those names go stale when an upstream
# dimension moves — the fillet then reports Invalid. This macro
# deletes the old rim fillets and re-picks the edges geometrically,
# which is why it is a separate step rather than part of the build.
# ============================================================

import FreeCAD as App
import Part

TOL = 0.02
# body, which face, feature name. "top"/"bottom" track the shape's own
# extremes; a number pins an explicit height.
#
# Body_Main's bottom is deliberately absent. The wall-mount tab is
# coplanar with that face and merges into it, so its perimeter is no
# longer a simple loop and OCC refuses the fillet ("BRep_API: command
# not done"). Cosmetic anyway, and that face lies against the wall — the
# faces a hand actually touches are the lid top and the door underside,
# and both still get rounded.
RIMS = (
    ("Body_Lid",  "top",    "Rim_LidTop"),
    ("Body_Door", "bottom", "Rim_DoorBottom"),
)

DOC = App.ActiveDocument
if DOC is None:
    raise RuntimeError("No active document — build the enclosure first.")

sheet = DOC.getObject("params")
r_expr = "params.edge_r" if sheet else None
r_val = sheet.get("edge_r") if sheet else 1.2


def rim_edges(shape, z):
    """Outer perimeter of the flat face sitting at height z."""
    found = []
    for f in shape.Faces:
        if not isinstance(f.Surface, Part.Plane):
            continue
        if abs(f.Surface.Axis.z) < 0.999:
            continue
        if abs(f.CenterOfMass.z - z) > TOL:
            continue
        found.extend(f.OuterWire.Edges)
    return found


def names_of(shape, edges):
    out = []
    for i, e in enumerate(shape.Edges, 1):
        for t in edges:
            if e.isSame(t):
                out.append("Edge%d" % i)
                break
    return out


done, skipped = [], []
for body_name, which, feat_name in RIMS:
    body = DOC.getObject(body_name)
    if body is None:
        skipped.append("%s: no such body" % body_name)
        continue

    # drop the previous rim fillet, restoring the tip beneath it
    old = DOC.getObject(feat_name)
    if old is not None:
        body.Tip = old.BaseFeature
        DOC.removeObject(old.Name)
        body.Tip.Visibility = True     # the restored tip must show again
        DOC.recompute()

    tip = body.Tip
    shape = tip.Shape
    bb = shape.BoundBox
    if isinstance(which, (int, float)):
        z = float(which)
    else:
        z = bb.ZMax if which == "top" else bb.ZMin
    names = names_of(shape, rim_edges(shape, z))
    if not names:
        skipped.append("%s: no %s rim found" % (body_name, which))
        continue

    f = body.newObject("PartDesign::Fillet", feat_name)
    f.Base = (tip, names)
    if r_expr:
        f.setExpression("Radius", r_expr)
    else:
        f.Radius = r_val
    tip.Visibility = False
    DOC.recompute()

    # A failed fillet leaves a null shape, and asking a null shape whether
    # it is valid raises rather than returning False — so probe it inside
    # a try, or one bad fillet takes the whole macro down with it.
    try:
        good = ("Error" not in str(f.State)) and f.Shape.isValid()
    except Exception:
        good = False

    if not good:
        skipped.append("%s: fillet failed — reduce edge_r, or the face is "
                       "interrupted by another feature" % body_name)
        body.Tip = f.BaseFeature
        DOC.removeObject(f.Name)
        body.Tip.Visibility = True
        DOC.recompute()
    else:
        done.append("%s (%d edges)" % (feat_name, len(names)))

# ------------------------------------------------------------
# Blends at the root of the wall-mount tab. Both ADD material: filleting
# a concave edge fills an inside corner rather than rounding an outside
# one. Neither can come from the tab's sketch, because the material they
# need sits outside both the tab rectangle and the box.
#
#   Blend_MountTab   the two vertical side junctions
#   Blend_MountRoot  the horizontal top junction. The tab is a cantilever
#                    carrying the whole box, so that line is both peak
#                    bending stress and a layer boundary straight across
#                    the load path — where it would crack.
# ------------------------------------------------------------
if sheet is not None:
    body = DOC.getObject("Body_Main")

    def num(alias):
        return float(sheet.get(alias))

    # Drop existing blends outermost first: removing a lower one while
    # something is still stacked on top of it orphans the feature above.
    for nm in ("Blend_MountRoot", "Blend_MountTab"):
        old = DOC.getObject(nm)
        if old is not None:
            body.Tip = old.BaseFeature
            DOC.removeObject(old.Name)
            body.Tip.Visibility = True
            DOC.recompute()

    try:
        x_j, y_j = num("out_l") / 2, num("mount_w") / 2
        z_hi = num("mount_t")
    except Exception:
        x_j = None

    def side_edges(shape):
        """Vertical lines where the tab's sides meet the end wall."""
        out = []
        for e in shape.Edges:
            if len(e.Vertexes) != 2:
                continue
            a, b = e.Vertexes[0].Point, e.Vertexes[1].Point
            if abs(a.x - b.x) > TOL or abs(a.y - b.y) > TOL:
                continue                       # want the vertical ones
            if abs(a.z - b.z) < TOL:
                continue
            if abs(a.x - x_j) > TOL or abs(abs(a.y) - y_j) > TOL:
                continue
            lo, hi = sorted((a.z, b.z))
            if lo < -TOL or hi > z_hi + TOL:
                continue
            out.append(e)
        return out

    def root_edges(shape):
        """The horizontal line where the tab's top face meets the wall."""
        out = []
        for e in shape.Edges:
            if len(e.Vertexes) != 2:
                continue
            a, b = e.Vertexes[0].Point, e.Vertexes[1].Point
            if abs(a.x - x_j) > TOL or abs(b.x - x_j) > TOL:
                continue
            if abs(a.z - z_hi) > TOL or abs(b.z - z_hi) > TOL:
                continue
            if abs(a.y - b.y) < TOL:
                continue                       # must run along Y
            out.append(e)
        return out

    def blend(feat_name, r_expr, picker, hint):
        tip = body.Tip
        shape = tip.Shape
        names = names_of(shape, picker(shape))
        if not names:
            skipped.append("%s: edges not found" % feat_name)
            return
        f = body.newObject("PartDesign::Fillet", feat_name)
        f.Base = (tip, names)
        f.setExpression("Radius", r_expr)
        tip.Visibility = False
        DOC.recompute()
        try:
            good = ("Error" not in str(f.State)) and f.Shape.isValid()
        except Exception:
            good = False
        if good:
            done.append("%s (%d edges)" % (feat_name, len(names)))
        else:
            skipped.append("%s: failed — reduce %s" % (feat_name, hint))
            body.Tip = f.BaseFeature
            DOC.removeObject(f.Name)
            body.Tip.Visibility = True
            DOC.recompute()

    if x_j is not None:
        blend("Blend_MountTab", "params.mount_blend",
              side_edges, "mount_blend")
        blend("Blend_MountRoot", "params.mount_root_r",
              root_edges, "mount_root_r")

DOC.recompute()
App.Console.PrintMessage("round-rims: %s\n" % (", ".join(done) or "nothing"))
for s in skipped:
    App.Console.PrintWarning("round-rims: %s\n" % s)
